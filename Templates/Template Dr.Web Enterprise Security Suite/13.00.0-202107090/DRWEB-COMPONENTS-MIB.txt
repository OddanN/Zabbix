DRWEB-COMPONENTS-MIB DEFINITIONS ::= BEGIN

IMPORTS
	mibs
		FROM DRWEB-MIB
        MODULE-IDENTITY
                FROM SNMPv2-SMI
        TEXTUAL-CONVENTION
                FROM SNMPv2-TC;

components MODULE-IDENTITY
	LAST-UPDATED "202106091318Z"
	ORGANIZATION "Doctor Web, Ltd."
	CONTACT-INFO "email: mibeditor@drweb.com"
	DESCRIPTION  "Doctor Web Enterprise Suite Protection Components MIB"
        REVISION     "202106091318Z"
        DESCRIPTION  "Doctor Web Enterprise Suite Protection Components MIB (2021-06-09)"
        ::= { mibs 1 }

AVComponent ::= TEXTUAL-CONVENTION
        STATUS        current
        DESCRIPTION   "Anti-Virus protection components."
        SYNTAX        INTEGER {
                                cDRWEB386(0),
                                cDRWEB2(1),
                                cDRWEBNW(2),
                                cDRWEBWCL(3),
                                cDRWEB32W(4),
                                cSPIDER9X(5),
                                cSPIDERNT(6),
                                cDRWEBLINUX(7),
                                cDRWEBFREEBSD(8),
                                cDAEMONLINUX(9),
                                cDAEMONFREEBSD(10),
                                cDAEMON2EMX(11),
                                cDAEMONSUNI86(12),
                                cDRWEBSUNI86(13),
                                cSPIDERMAILHOME(14),
                                cDRWEBOPENBSD(15),
                                cDAEMONOPENBSD(16),
                                cDRWEBNETBSD(17),
                                cDAEMONNETBSD(18),
                                cCCHOME(19),
                                cCSNT(20),
                                cCSLINUX(21),
                                cCSFREEBSD(22),
                                cCSOPENBSD(23),
                                cCSNETBSD(24),
                                cCSSUNI86(25),
                                cDRWEBTHEBATPLUGIN(26),
                                cDRWEBLOTUSSERVER(27),
                                cDRWEBUPDATE(28),
                                cWINCGPPLUGIN(29),
                                cENTERPRISEAGENT(30),
                                cSCHEDULER(31),
                                cANTISPAM(32),
                                cPLESKWIN(33),
                                cSPIDERNTSERVER(34),
                                cENTERPRISENTREG(35),
                                cENTERPRISEUI(36),
                                cENTERPRISESCAN(37),
                                cSPIDERGATE(38),
                                cUNIXAGENT(39),
                                cMAILDLINUX(40),
                                cENTERPRISESRVREG(41),
                                cLNSFW(42),
                                cMAILDSUNI86(43),
                                cMAILDFREEBSD(44),
                                cDRWEBEXCHANGE(45),
                                cUNIXMONITOR(46),
                                cMAILD(47),
                                cAVDESKSERVER(48),
                                cICAPLINUX(49),
                                cICAPSUN86(50),
                                cICAPFREEBSD(51),
                                cMIMESWEEPER(52),
                                cDRWEBWINMOBILE(53),
                                cPARENTALCONTROL(54),
                                cVADERETRO(55),
                                cMAILDESK(56),
                                cSPIDERG3WKS(57),
                                cSPIDERG3SRV(58),
                                cDRWEBNWOTF(59),
                                cWINMOBILEMON(60),
                                cSPIDERLINUX(61),
                                cESCANUNIX(62),
                                cSCANNERSE(63),
                                cKERIOPLUGIN(100),
                                cDRWEBMAC(101),
                                cCURENET(102),
                                cOUTLOOK(103),
                                cWINGATEPLUGIN(104),
                                cFIREWALL(105),
                                cDRWEBMACMON(106),
                                cESCANMAC(107),
                                cUNIXNSS(108),
                                cMACSERVER(109),
                                cSMBSPIDERLINUX(110),
                                cSMBSPIDERFREEBSD(111),
                                cSMBSPIDERSUNI86(112),
                                cMACSERVERMON(113),
                                cANDROID(114),
                                cANDROIDMON(115),
                                cANDROIDANTISPAM(116),
                                cANDROIDANTITHEFT(117),
                                cANDROIDAPPFILTER(118),
                                cANDROIDSCANNER(119),
                                cMACLIGHT(120),
                                cISASERVER(121),
                                cAVREMOTECONTROL(122),
                                cANDROIDCLOUD(123),
                                cSELFPROTECTION(124),
                                cTRAFFICINSPECTOR(125),
                                cOUTLOOKANTISPAM(126),
                                cKERIOCONNECT(127),
                                cSCANENGINELINUX(128),
                                cFILECHECKLINUX(129),
                                cAGENTLINUX(130),
                                cSCANENGINEFREEBSD(131),
                                cFILECHECKFREEBSD(132),
                                cAGENTFREEBSD(133),
                                cSCANENGINESUNI86(134),
                                cFILECHECKSUNI86(135),
                                cAGENTSUNI86(136),
                                cPUBLICCLIENT(137),
                                cSCANENGINEMAC(138),
                                cFILECHECKMAC(139),
                                cAGENTMAC(140),
                                cGATEMAC(141),
                                cGATEMACSERVER(142),
                                cGATELINUX(143),
                                cPREVENTIVEPROTECTION(144),
                                cESNETWORKSET(145),
                                cESPROXY(146),
                                cSHAREPOINT(147),
                                cMSSRVPLUGINS(148),
                                cNETFILTER(149),
                                cLOTUSANTISPAM(150),
                                cCLAMDLINUX(151),
                                cCLAMDFREEBSD(152),
                                cCLAMDSUNI86(153),
                                cAPPCONTROL(154),
                                cMESHDAEMON(155),
                                cMESHCLIENT(156)
                              }
END
